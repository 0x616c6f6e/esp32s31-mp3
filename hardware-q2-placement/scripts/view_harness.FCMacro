"""Open only the generated connector planning assembly; save its review view."""
import FreeCAD as App,FreeCADGui as Gui
from pathlib import Path
from PySide import QtCore
P=Path(__file__).resolve().parents[2]/'mechanical/connector-layout'
d=App.openDocument(str(P/'Q2_Connector_Layout.FCStd'))
for o in d.Objects:
    if not hasattr(o,'Shape'):continue
    name=o.Name;o.ViewObject.ShapeColor=(.28,.30,.33);o.ViewObject.LineColor=(.12,.14,.17)
    o.ViewObject.Visibility=True
    o.ViewObject.DisplayMode='Flat Lines'
    if name=='HousingWithControlPosts':o.ViewObject.ShapeColor=(.70,.73,.77)
    if name=='RearCoverWithPCBPosts':o.ViewObject.Visibility=False
    if name=='MainPCB':o.ViewObject.ShapeColor=(.08,.38,.23)
    if name=='BatteryReference':o.ViewObject.ShapeColor=(.70,.78,.88);o.ViewObject.Transparency=72
    if name in ['LCDModule','ControlBoard','ControlBoardFasteners']:o.ViewObject.Visibility=False
    if name=='Motor_C08_005':o.ViewObject.ShapeColor=(.90,.62,.18)
    if name=='MotorHolderProposal':o.ViewObject.ShapeColor=(.76,.45,.18)
    if name.startswith('MotorWire'):o.ViewObject.ShapeColor=(.95,.55,.13)
    if name.startswith('BatteryWire'):o.ViewObject.ShapeColor={'BatteryWire1':(.80,.12,.15),'BatteryWire2':(.95,.78,.15),'BatteryWire3':(.15,.17,.20)}[name]
    if 'FPC' in name:o.ViewObject.ShapeColor=(.87,.61,.24)
    if name in ['PCB_H1','PCB_H2']:o.ViewObject.ShapeColor=(.95,.94,.88)
Gui.activeDocument().activeView().viewAxonometric();Gui.activeDocument().activeView().fitAll()
def finish():
    Gui.activeDocument().activeView().saveImage(str(P/'assembly-isometric.png'),1400,1400,'White')
    Gui.activeDocument().activeView().viewTop();Gui.activeDocument().activeView().fitAll()
    QtCore.QTimer.singleShot(700,finish_top)
def finish_top():
    Gui.activeDocument().activeView().saveImage(str(P/'assembly-top.png'),1000,1500,'White')
    Gui.activeDocument().activeView().viewAxonometric();Gui.activeDocument().activeView().fitAll()
    QtCore.QTimer.singleShot(700,save_document)
def save_document():
    d.recompute();d.save()
    (P/'render-complete.txt').write_text('Cutaway view: LCD, control board, fasteners and rear cover hidden; reveal in tree as needed.\n',encoding='utf8')
    App.closeDocument(d.Name)
    QtCore.QTimer.singleShot(200,Gui.getMainWindow().close)
QtCore.QTimer.singleShot(1200,finish)
