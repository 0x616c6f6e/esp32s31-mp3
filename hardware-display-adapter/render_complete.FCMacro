from pathlib import Path
import FreeCAD as A,FreeCADGui as G
from PySide import QtCore
O=Path(r'C:/Users/alon/Desktop/Preoject/esp32s31-mp3/hardware-display-adapter/am213-fpc-adapter')
d=A.openDocument(str(O/'models3d/Q2_L_AM213_Completed_Adapter.FCStd'))
def render():
 try:
  for o in d.Objects:
   if hasattr(o,'Group'):o.ViewObject.Visibility=True
  for o in d.Objects:
   if hasattr(o,'Shape') and not hasattr(o,'Group'):
    o.ViewObject.Visibility=o.Name.startswith('Adapter') and o.Name!='AdapterBTBMax'
    if o.Name in ['AdapterFoldedFlex','AdapterSubstrate']:o.ViewObject.ShapeColor=(.83,.52,.12)
    elif 'Stiffener' in o.Name:o.ViewObject.ShapeColor=(.2,.25,.3)
    elif o.Name.startswith('Adapter_R') or o.Name=='Adapter_J2':o.ViewObject.ShapeColor=(.22,.23,.25)
    else:o.ViewObject.ShapeColor=(.68,.59,.4)
    o.ViewObject.DisplayMode='Flat Lines'
  v=G.activeDocument().activeView();v.viewAxonometric();v.fitAll();G.updateGui()
  v.saveImage(str(O/'output/adapter-folded.png'),1800,1100,'White')
  for n in ['HousingControlsA','MainPCB','PCB_FPC2','LCDModule','ScreenRearFPCEnvelope']:
   ob=d.getObject(n)
   if ob:
    ob.ViewObject.Visibility=True;ob.ViewObject.Transparency=80 if n!='PCB_FPC2' else 0
    if n=='HousingControlsA':ob.ViewObject.ShapeColor=(.6,.7,.8)
  v.viewAxonometric();v.fitAll();G.updateGui();v.saveImage(str(O/'output/adapter-in-enclosure.png'),1600,1500,'White')
  for n in ['DisplayAdapterPCB','DisplayAdapterConnectors']:
   ob=d.getObject(n)
   if ob:ob.ViewObject.Visibility=False
  d.save();(O/'output/render-complete.txt').write_text('Completed fit document saved with adapter visible, replaced placeholders hidden.')
 except Exception:
  import traceback
  (O/'output/render-error.txt').write_text(traceback.format_exc())
 G.getMainWindow().close()
QtCore.QTimer.singleShot(1500,render)
